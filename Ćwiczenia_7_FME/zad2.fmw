FME workspace zad2.fmw

Parameters:
- SourceDataset_GEOTIFF = ""$(FME_MF_DIR)rastry\HP.tif" "$(FME_MF_DIR)rastry\HT.tif" "$(FME_MF_DIR)rastry\HU.tif" "$(FME_MF_DIR)rastry\HW.tif" "$(FME_MF_DIR)rastry\HX.tif" "$(FME_MF_DIR)rastry\HY.tif" "$(FME_MF_DIR)rastry\HZ.tif" "$(FME_MF_DIR)rastry\NA.tif" "$(FME_MF_DIR)rastry\NB.tif" "$(FME_MF_DIR)rastry\NC.tif" "$(FME_MF_DIR)rastry\ND.tif" "$(FME_MF_DIR)rastry\NF.tif" "$(FME_MF_DIR)rastry\NG.tif" "$(FME_MF_DIR)rastry\NH.tif" "$(FME_MF_DIR)rastry\NJ.tif" "$(FME_MF_DIR)rastry\NK.tif" "$(FME_MF_DIR)rastry\NL.tif" "$(FME_MF_DIR)rastry\NM.tif" "$(FME_MF_DIR)rastry\NN.tif" "$(FME_MF_DIR)rastry\NO.tif" "$(FME_MF_DIR)rastry\NR.tif" "$(FME_MF_DIR)rastry\NS.tif" "$(FME_MF_DIR)rastry\NT.tif" "$(FME_MF_DIR)rastry\NU.tif" "$(FME_MF_DIR)rastry\NW.tif" "$(FME_MF_DIR)rastry\NX.tif" "$(FME_MF_DIR)rastry\NY.tif" "$(FME_MF_DIR)rastry\NZ.tif" "$(FME_MF_DIR)rastry\OV.tif" "$(FME_MF_DIR)rastry\SC.tif" "$(FME_MF_DIR)rastry\SD.tif" "$(FME_MF_DIR)rastry\SE.tif" "$(FME_MF_DIR)rastry\SH.tif" "$(FME_MF_DIR)rastry\SJ.tif" "$(FME_MF_DIR)rastry\SK.tif" "$(FME_MF_DIR)rastry\SM.tif" "$(FME_MF_DIR)rastry\SN.tif" "$(FME_MF_DIR)rastry\SO.tif" "$(FME_MF_DIR)rastry\SP.tif" "$(FME_MF_DIR)rastry\SR.tif" "$(FME_MF_DIR)rastry\SS.tif" "$(FME_MF_DIR)rastry\ST.tif" "$(FME_MF_DIR)rastry\SU.tif" "$(FME_MF_DIR)rastry\SV.tif" "$(FME_MF_DIR)rastry\SW.tif" "$(FME_MF_DIR)rastry\SX.tif" "$(FME_MF_DIR)rastry\SY.tif" "$(FME_MF_DIR)rastry\SZ.tif" "$(FME_MF_DIR)rastry\TA.tif" "$(FME_MF_DIR)rastry\TF.tif" "$(FME_MF_DIR)rastry\TG.tif" "$(FME_MF_DIR)rastry\TL.tif" "$(FME_MF_DIR)rastry\TM.tif" "$(FME_MF_DIR)rastry\TQ.tif" "$(FME_MF_DIR)rastry\TR.tif" "$(FME_MF_DIR)rastry\TV.tif""   # Source GeoTIFF File(s) or URL(s)
- DestDataset_FILEGDB = $(FME_MF_DIR)rastry\Results.gdb   # File Geodatabase

Readers:
- GEOTIFF_1: GEOTIFF from $(SourceDataset_GEOTIFF)

Writers:
- FILEGDB_1: FILEGDB to $(DestDataset_FILEGDB)

GEOTIFF (reader GEOTIFF_1)
    -> Reprojector
Reprojector
    DEST = LL-WGS84
    INTERPOLATION_TYPE_NAME = Nearest Neighbor
    RASTER_CELL_SIZE = Preserve Cells
    RASTER_TOLERANCE = 0.0
    REPROJECTED -> RasterPropertyExtractor
RasterPropertyExtractor
    -> AttributeCreator
AttributeCreator
    ATTR_TABLE = SET_TO path (varchar(200)) = $(FME_MF_DIR_ENCODED)rastry\@Value(fme_basename).tif
    -> FilePropertyExtractor
FilePropertyExtractor
    FMT = FME Date/Time (%Y%m%d%H%M%S)
    PATH = @Value(path)
    -> AttributeCreator_2
AttributeCreator_2
    ATTR_TABLE = SET_TO NewName (varchar(200)) = @Value(fme_basename)_@Value(_file_size)
    -> Extents (writer FILEGDB_1)
Extents (writer FILEGDB_1)

FME custom transformer FilePropertyExtractor
Extracts basic properties of a file or a directory and adds these attributes to the feature.
    _file_type
    : holds "File" or "Directory", which indicates whether the specified path is a file or a directory.
    _file_size
    : holds the size of file/directory in bytes (total of file sizes if directory)
    _file_atime
    : holds the time of last access.
    _file_mtime
    : holds the time of last modification.
    _file_ctime
    : holds the time of creation on some systems (like Windows), or the time of last metadata change on other systems (like Unix).
    You can specify the format of "_file_atime", "_file_mtime", and "_file_ctime" via the "Date/Time Format" parameter.
    The input feature will be output from the 
    <Rejected>
    port if the specified file/directory does not exist, the path indicates a symbolic link, or an unexpected error has occurred. 
    This transformer contains a Python script, which was tested with both Python 2.7 and Python 3.4 interpreter.
Parameters
    File/Directory Path
    :
    Specify the path of a file or a directory.
    Date/Time Format
    :
    Specify a date/datetime/time format that should be applied to the values of "_file_atime", "_file_mtime", and "_file_ctime". 
    The format syntax is the same as the DateFormatter. See the help doc on the transformer.

Parameters:
- PATH =   # File/Directory Path
- FMT = FME Date/Time (%Y%m%d%H%M%S)

Input (input)
    -> ParameterFetcher
ParameterFetcher
    ATTR_LIST = __filepropertyextractor.path {$(PATH)}
    -> PythonCaller
PythonCaller
    NEW_ATTRIBUTES = _file_type _file_size _file_atime _file_mtime _file_ctime __filepropertyextractor.error
    PYTHONSOURCE:
      # 2016-05-25, Takashi Iijima, Original Implementation
      # 2020-01-28, Takashi Iijima, Calculate Directory Size as Total File Sizes under the Directory; Changed Default Python Interpreter to 3.6+

      import fme, fmeobjects
      import os
      def extractFileProperty(feature):
          def get_dir_size(path):
              total = 0
              for p in os.listdir(path):
                  full_path = os.path.join(path, p)
                  if os.path.isfile(full_path):
                      total += os.path.getsize(full_path)
                  elif os.path.isdir(full_path):
                      total += get_dir_size(full_path)
              return total
          try:
              path = feature.getAttribute('__filepropertyextractor.path')
              if os.path.exists(path) and not os.path.islink(path):
                  s = os.stat(path)
                  if os.path.isdir(path):
                      feature.setAttribute('_file_type', 'Directory')
                      feature.setAttribute('_file_size', get_dir_size(path))
                  else:
                      feature.setAttribute('_file_type', 'File')
                      feature.setAttribute('_file_size', s.st_size)
                  feature.setAttribute('_file_atime', int(s.st_atime))
                  feature.setAttribute('_file_mtime', int(s.st_mtime))
                  feature.setAttribute('_file_ctime', int(s.st_ctime))
              else:
                  raise Exception('specified file/directory does not exist')
          except Exception as ex:
              feature.setAttribute('__filepropertyextractor.error', '%s' % ex)
    PYTHONSYMBOL = extractFileProperty
    -> Tester
Tester
    BOOL_OP = OR
    TEST_CLAUSE = TEST __filepropertyextractor.error ATTRIBUTE_IS_MISSING ""
    TEST_MODE = Automatic
    PASSED -> AttributeRemover
    FAILED -> AttributeRemover_2
AttributeRemover
    REMOVE_ATTRS = __filepropertyextractor.path,__filepropertyextractor.error
    -> DateFormatter
DateFormatter
    DATE_ATTR = _file_ctime,_file_mtime,_file_atime
    FMT = $(FMT)
    INVALID_DATE_VALUE = _FME_NO_OP_
    SRCFMT = %s
    -> Output (output)
Output (output)
AttributeRemover_2
    REMOVE_ATTRS = _file_size,_file_type,_file_ctime,__filepropertyextractor.path,_file_mtime,_file_atime
    -> AttributeRenamer
AttributeRenamer
    ATTR_TABLE = RENAME_SET_DEFAULT __filepropertyextractor.error > _rejected_reason
    -> <Rejected> (output)
<Rejected> (output)
